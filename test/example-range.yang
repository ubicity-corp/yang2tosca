// Contents of "example-range.yang"
module example-range {
  yang-version 1.1;
  namespace "urn:example:range";
  prefix "sys";

  organization "Example Inc.";
  contact "joe@example.com";
  description
    "The module for entities implementing the Example system.";

  revision 2007-06-09 {
    description "Initial revision.";
  }

   typedef my-type1 {
     type int32 {
       range "11..256";
     }
   }

   typedef my-type2 {
     type int32 {
       range "11..max";
     }
   }

   typedef my-type3 {
     type int32 {
       range "11";
     }
   }

   typedef my-type4 {
     type int32 {
       range "min..max";
     }
   }

   typedef my-type5 {
     type int32 {
       range "min..256";
     }
   }

  typedef my-base-int32-type {
       type int32 {
         range "1..4 | 10..20";
       }
     }

  typedef my-decimal {
     type decimal64 {
         fraction-digits 2;
         range "min .. 3.14 | 10 | 20..max";
       }
     }
}
